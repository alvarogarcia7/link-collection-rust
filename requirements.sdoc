[DOCUMENT]
TITLE: Link Collection Rust - Requirements
VERSION: 1.0

[SECTION]
TITLE: System Requirements

[REQUIREMENT]
UID: SYSREQ-001
TITLE: Read existing database files
STATEMENT: The system shall support reading and processing existing database files to retrieve link collection data.
STATUS: Active

[REQUIREMENT]
UID: SYSREQ-002
TITLE: Create a CLI application
STATEMENT: The system shall provide a command-line interface with top-level commands and multiple subcommands for managing link collections.
STATUS: Active

[REQUIREMENT]
UID: SYSREQ-003
TITLE: Add a new record to the database
STATEMENT: The system shall allow users to add new records to the database through the CLI and temporary file uploads.
STATUS: Active

[REQUIREMENT]
UID: SYSREQ-004
TITLE: Retrieve items from database
STATEMENT: The system shall support retrieval and querying of items from the database.
STATUS: Active

[REQUIREMENT]
UID: SYSREQ-005
TITLE: Download items from HackerNews
STATEMENT: The system shall download link items from HackerNews and persist them to the database with publication date metadata.
STATUS: Active

[REQUIREMENT]
UID: SYSREQ-006
TITLE: Create a wrapper on top of recutils library
STATEMENT: The system shall provide a wrapper abstraction over the recutils library for database operations.
STATUS: Active

[REQUIREMENT]
UID: SYSREQ-007
TITLE: Replace Go Stubs with Rust Stubs
STATEMENT: The system shall migrate from Go-based stub implementations to pure Rust stub implementations for all external dependencies.
STATUS: Active

[SECTION]
TITLE: High-Level Requirements

[REQUIREMENT]
UID: HLR-001-1
TITLE: Dump the contents into the console
STATEMENT: The system shall be able to read database files and output their contents to the console for inspection and debugging.
STATUS: Approved
RELATIONS:
- TYPE: Parent
  VALUE: SYSREQ-001

[REQUIREMENT]
UID: HLR-001-2
TITLE: Use a fixed template to print to console
STATEMENT: The system shall support printing database contents using a predefined template format for consistent output.
STATUS: Approved
RELATIONS:
- TYPE: Parent
  VALUE: SYSREQ-001

[REQUIREMENT]
UID: HLR-001-3
TITLE: Use any template to print to console
STATEMENT: The system shall allow users to specify custom templates for printing database contents to the console.
STATUS: Approved
RELATIONS:
- TYPE: Parent
  VALUE: SYSREQ-001

[REQUIREMENT]
UID: HLR-001-4
TITLE: Read the existing date formats
STATEMENT: The system shall parse and handle multiple date formats present in existing database files.
STATUS: Approved
RELATIONS:
- TYPE: Parent
  VALUE: SYSREQ-001

[REQUIREMENT]
UID: HLR-001-5
TITLE: Add the optional field 'Link'
STATEMENT: The system shall support reading and processing the optional 'Link' field from database records.
STATUS: Approved
RELATIONS:
- TYPE: Parent
  VALUE: SYSREQ-001

[REQUIREMENT]
UID: HLR-006-1
TITLE: Use clap for top command and multiple subcommands
STATEMENT: The system shall use the clap crate for command-line argument parsing to support hierarchical commands and subcommands.
STATUS: Approved
RELATIONS:
- TYPE: Parent
  VALUE: SYSREQ-002

[REQUIREMENT]
UID: HLR-006-2
TITLE: Add a logger
STATEMENT: The system shall include logging functionality for debugging and tracing application execution.
STATUS: Approved
RELATIONS:
- TYPE: Parent
  VALUE: SYSREQ-002

[REQUIREMENT]
UID: HLR-006-3
TITLE: Add a configuration system
STATEMENT: The system shall provide configuration management to avoid repeating hardcoded values throughout the application.
STATUS: Approved
RELATIONS:
- TYPE: Parent
  VALUE: SYSREQ-002

[REQUIREMENT]
UID: HLR-006-4
TITLE: Read the configuration from a file
STATEMENT: The system shall read configuration values from TOML files with support for multiple sources and priority levels.
STATUS: Approved
RELATIONS:
- TYPE: Parent
  VALUE: SYSREQ-002

[REQUIREMENT]
UID: HLR-006-5
TITLE: List the tags from the database
STATEMENT: The system shall provide a command to list all tags present in the database with counts and metadata.
STATUS: Approved
RELATIONS:
- TYPE: Parent
  VALUE: SYSREQ-002

[REQUIREMENT]
UID: HLR-002-1
TITLE: Add record from the CLI
STATEMENT: The system shall allow users to add new records to the database through command-line interface input.
STATUS: Approved
RELATIONS:
- TYPE: Parent
  VALUE: SYSREQ-003

[REQUIREMENT]
UID: HLR-002-2
TITLE: Add record from a temporary file
STATEMENT: The system shall allow users to add new records to the database from temporary file uploads.
STATUS: Approved
RELATIONS:
- TYPE: Parent
  VALUE: SYSREQ-003

[REQUIREMENT]
UID: HLR-002-3
TITLE: Print the record in the same order as it was provided
STATEMENT: The system shall maintain and respect the original field order when printing records that were added to the database.
STATUS: Approved
RELATIONS:
- TYPE: Parent
  VALUE: SYSREQ-003

[REQUIREMENT]
UID: HLR-004-1
TITLE: Create a new stubbed HTTP server
STATEMENT: The system shall include a stubbed HTTP server for testing HackerNews download functionality.
STATUS: Approved
RELATIONS:
- TYPE: Parent
  VALUE: SYSREQ-005

[REQUIREMENT]
UID: HLR-004-2
TITLE: Download the items from a URL
STATEMENT: The system shall fetch link items from a given HackerNews URL endpoint and parse the response.
STATUS: Approved
RELATIONS:
- TYPE: Parent
  VALUE: SYSREQ-005

[REQUIREMENT]
UID: HLR-004-3
TITLE: Commit to git using the date of publishing
STATEMENT: The system shall create git commits for downloaded HackerNews items using their original publication date as the commit date.
STATUS: Approved
RELATIONS:
- TYPE: Parent
  VALUE: SYSREQ-005

[REQUIREMENT]
UID: HLR-007-1
TITLE: Create Rust Stubs for existing Go Stubs
STATEMENT: The system shall replace all Go stub implementations with equivalent Rust implementations without changing external behavior.
STATUS: Approved
RELATIONS:
- TYPE: Parent
  VALUE: SYSREQ-007

[SECTION]
TITLE: Low-Level Requirements

[REQUIREMENT]
UID: LLR-006-4-1
TITLE: Configuration file in TOML format
STATEMENT: Configuration files shall use TOML format for human readability and structured data representation.
RELATIONS:
- TYPE: Parent
  VALUE: HLR-006-4

[REQUIREMENT]
UID: LLR-006-4-2
TITLE: Read config from user home directory
STATEMENT: The system shall read configuration from ~/.config/lc/config.toml as the default configuration location.
RELATIONS:
- TYPE: Parent
  VALUE: HLR-006-4

[REQUIREMENT]
UID: LLR-006-4-3
TITLE: Read config from .env.local file
STATEMENT: The system shall support overriding configuration values from a .env.local file in the current working directory.
RELATIONS:
- TYPE: Parent
  VALUE: HLR-006-4

[REQUIREMENT]
UID: LLR-006-4-4
TITLE: Read config from environment variable
STATEMENT: The system shall support overriding configuration via LC_CONFIG_FILE environment variable.
RELATIONS:
- TYPE: Parent
  VALUE: HLR-006-4

[REQUIREMENT]
UID: LLR-006-4-5
TITLE: Read config from command line argument
STATEMENT: The system shall support overriding configuration via --config-file command-line argument.
RELATIONS:
- TYPE: Parent
  VALUE: HLR-006-4

[REQUIREMENT]
UID: LLR-006-4-6
TITLE: Configuration contains database_file
STATEMENT: Configuration shall include database_file field specifying the path to the database file.
RELATIONS:
- TYPE: Parent
  VALUE: HLR-006-4

[REQUIREMENT]
UID: LLR-006-4-7
TITLE: Configuration contains log_level
STATEMENT: Configuration shall include log_level field specifying the logging level.
RELATIONS:
- TYPE: Parent
  VALUE: HLR-006-4

[REQUIREMENT]
UID: LLR-006-4-8
TITLE: Configuration contains template_file
STATEMENT: Configuration shall include template_file field specifying the path to the output template file.
RELATIONS:
- TYPE: Parent
  VALUE: HLR-006-4

[REQUIREMENT]
UID: LLR-006-4-9
TITLE: Configuration contains hacker_news_url
STATEMENT: Configuration shall include hacker_news_url field specifying the URL for HackerNews item downloads.
RELATIONS:
- TYPE: Parent
  VALUE: HLR-006-4

[REQUIREMENT]
UID: LLR-006-4-10
TITLE: Create struct to hold configuration values
STATEMENT: A struct shall be created to hold all configuration values with proper type definitions and defaults.
RELATIONS:
- TYPE: Parent
  VALUE: HLR-006-4

[REQUIREMENT]
UID: LLR-006-4-11
TITLE: Implement configuration file merging
STATEMENT: The system shall merge configuration values from multiple sources respecting priority order.
RELATIONS:
- TYPE: Parent
  VALUE: HLR-006-4

[REQUIREMENT]
UID: LLR-006-4-12
TITLE: Include configuration in logging setup
STATEMENT: The logger shall be configured using the log_level from configuration.
RELATIONS:
- TYPE: Parent
  VALUE: HLR-006-4

[REQUIREMENT]
UID: LLR-006-4-13
TITLE: Include configuration in database connection
STATEMENT: Database connection logic shall use the database_file from configuration.
RELATIONS:
- TYPE: Parent
  VALUE: HLR-006-4

[REQUIREMENT]
UID: LLR-006-4-14
TITLE: Include configuration in template rendering
STATEMENT: Template rendering logic shall use the template_file from configuration.
RELATIONS:
- TYPE: Parent
  VALUE: HLR-006-4

[REQUIREMENT]
UID: LLR-006-4-15
TITLE: Include configuration in HackerNews download
STATEMENT: HackerNews download logic shall use the hacker_news_url from configuration.
RELATIONS:
- TYPE: Parent
  VALUE: HLR-006-4
